module ietf-ni-location {
  yang-version 1.1;
  namespace "urn:ietf:params:xml:ns:yang:ietf-ni-location";
  prefix nilo;

  import ietf-yang-types {
    prefix yang;
    reference
      "RFC 9911: Common YANG Data Types";
  }
  import ietf-network-inventory {
    prefix nwi;
    reference
      "RFCAAAA: A YANG Data Model for Network Inventory";
  }
  import ietf-geo-location {
    prefix geo;
    reference
      "RFC 9179: A YANG Grouping for Geographic Locations";
  }

  organization
    "IETF Network Inventory YANG (ivy) Working Group";
  contact
    "WG Web:   https://datatracker.ietf.org/wg/ivy
     WG List:  IVY <mailto:ivy@ietf.org>

     Editor: Bo Wu
          <lana.wubo@huawei.com>
     Editor: Sergio Belotti
          <s.belotti.ietf@gmail.com>
     Editor: Jean-Francois Bouquier
          <jeff.bouquier@vodafone.com>
     Editor: Fabio Peruzzini
          <fabio.peruzzini@fibercop.com>
     Editor: Phil Bedard
          <phbedard@cisco.com>";
  description
    "This module defines a YANG model for Network Inventory
     location.

     Copyright (c) 2026 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).


     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     This version of this YANG module is part of RFC XXXX; see
     the RFC itself for full legal notices.";

  revision 2026-11-06 {
    description
      "Initial version";
    reference
      "RFC XXXX: A YANG Data Model for Network Inventory location.";
    //RFC Editor: Please replace XXXX with actual RFC number,
    //update date information and remove this note
  }

  /* Identities */
  /* Identities for rack classification */

  identity rack-class-type {
    description
      "Base identity for generic rack classification based on
       physical security characteristics. This identity is
       designed to be extended by regional, operator, or
       vendor-specific rack classes. It provides security
       metadata for rack cabinets indicating whether access
       requires a key or credential managed under a security
       process.";
  }

  identity rack-standard {
    base rack-class-type;
    description
      "Standard general-purpose rack. Access to the rack
       does not require a key or credential managed through
       a security process.";
  }

  identity rack-secure-baseline {
    base rack-class-type;
    description
      "Lockable rack. Access requires a key or credential
       managed through the operator's security process.
       The specific type is deployment-specific, and may
       include a mechanical key, electronic card, or lock
       code. Finer security class types are defined via
       derived identities.";
  }

  /* Typedef */

  typedef ni-location-ref {
    type leafref {
      path "/nwi:network-inventory/nilo:locations/nilo:location"
         + "/nilo:id";
    }
    description
      "This type is used by data models that need to reference
       network inventory location.";
  }

  /* Grouping */

  augment "/nwi:network-inventory" {
    description
      "Provides location and rack information for
       network inventory.";
    container locations {
      config false;
      description
        "Container for the location information.";
      list location {
        key "id";
        description
          "List of locations within the network. The 'id' leaf is the
           key and MUST be unique across all location entries; it is
           not scoped to the parent location. Short human-readable
           labels may be used, but they must be qualified when they
           would collide under different parents.
           The 'name' node is for display and has no global uniqueness
           requirement.";
        leaf id {
          type string;
          description
            "An identifier of the location, globally unique.";
        }
        uses nwi:basic-common-entity-attributes;
        leaf type {
          type string;
          description
            "The type of network inventory location, e.g.
             equipment room, building, or site.
             This allows operators to flexibly define custom location
             types (e.g., 'building', 'room', 'roof') based on their
             specific network scenarios without requiring model
             extensions. String-based types enable dynamic adaptation
             to heterogeneous organizational naming conventions.
             Operators are advised to maintain a controlled
             vocabulary for these values to avoid inconsistent
             spellings and free-text variants.";
        }
        leaf parent {
          type leafref {
            path "../../location/id";
          }
          description
            "The identifier of the location that physically contains
             this location.";
        }
        list contained-chassis {
          key "chassis-id";
          description
            "Chassis directly deployed in this location without a
             rack. chassis-id is a location-local identifier used to
             distinguish chassis instances within this location.
             It is not a global chassis identifier";
          leaf chassis-id {
            type string;
            description
              "Unique identifier for this chassis instance local
               to the containing location.";
          }
          uses nwi:component-ref;
        }
        leaf timestamp {
          type yang:date-and-time;
          description
            "Timestamp when the location was last updated.";
        }
        leaf valid-until {
          type yang:date-and-time;
          description
            "The timestamp for which this location is valid until.
             If unspecified, the location has no specific
             expiration time.";
        }
        container physical-address {
          description
            "Top-level container for the physical address.";
          leaf address {
            type string;
            description
              "Specifies an address (number and street).";
          }
          leaf postal-code {
            type string;
            description
              "Specifies a postal code.";
          }
          leaf state {
            type string;
            description
              "Specifies a state. This leaf can also be
               used to describe a region for a country that
               does not have states.";
          }
          leaf city {
            type string;
            description
              "Specifies a city.";
          }
          leaf country-code {
            type string {
              pattern '[A-Z]{2}';
            }
            description
              "Specifies a country.
               Expressed as ISO ALPHA-2 code.";
          }
        }
        uses geo:geo-location;
      }
    }
    container racks {
      config false; // Enforce Read-Only
      description
        "Top-level container for the list of racks.";
      list rack {
        key "id";
        description
          "List of racks within the inventory location (e.g., in an
           equipment room). A rack is an inventory asset in its own
           right, not a subtype of location. it references the
           location where it is placed via location-ref.
           Rack-internal chassis positioning uses relative-position
           (e.g., U-slot), reflecting the rack as a physical container";
        leaf id {
          type string;
          description
            "An identifier that uniquely identifies the rack.";
        }
        leaf rack-class {
          type identityref {
            base rack-class-type;
          }
          description
            "Classification of the rack for physical-security
               unlock process.";
        }
        uses nwi:basic-common-entity-attributes;
        container rack-location {
          description
            "The location information of the rack, which comprises
             the location reference, row number, and column number.";
          leaf location-ref {
            type ni-location-ref;
            description
              "Reference to the location where this rack is placed.";
          }
          leaf row-number {
            type uint32;
            description
              "Identifies the row within the location where
               the rack is located.";
          }
          leaf column-number {
            type uint32;
            description
              "Identifies the column within the location where
               the rack is located.";
          }
        }
        list contained-chassis {
          key "relative-position";
          description
            "The list of chassis within a rack. relative-position
             (e.g., U-slot) locates the chassis within this rack.";
          leaf relative-position {
            type uint8;
            description
              "Relative position (e.g., U-slot) of chassis within
               the rack.";
          }
          uses nwi:component-ref;
        }
        leaf height {
          type uint16;
          units "millimeter";
          description
            "Physical height of the rack.";
        }
        leaf width {
          type uint16;
          units "millimeter";
          description
            "Physical width of the rack.";
        }
        leaf depth {
          type uint16;
          units "millimeter";
          description
            "Physical depth of the rack.";
        }
        leaf max-voltage {
          type uint16;
          units "volt";
          description
            "The maximum voltage supported by the rack.";
        }
        leaf max-allocated-power {
          type uint32;
          units "watts";
          description
            "The maximum allocated power for the rack.";
        }
        leaf timestamp {
          type yang:date-and-time;
          description
            "Timestamp when the rack information was last updated.";
        }
        leaf valid-until {
          type yang:date-and-time;
          description
            "The timestamp for which this rack is valid until.
             If unspecified, the rack has no specific
             expiration time.";
        }
      }
    }
  }
}
